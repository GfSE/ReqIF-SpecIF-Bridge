# TC 1000 'Simple Content'

# Specification

## R1
- TC1000T: true
- TC1000F: false
- TC1000 Integer: 5000
- TC1000 String: Plain
- TC1000 Real: 1234.5
- TC1000 Date: 2002-05-30T09:30:10+06:00
- TC1000 Enum: TC1000 Yellow
- TC1000 Enum MultiValue: TC1000 Yellow, TC1000 Red, TC1000 Green
