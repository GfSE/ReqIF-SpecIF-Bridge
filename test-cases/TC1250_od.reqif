# TC 1250 'External Files'

# Specification

## R1
- TC1250 XHTML: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

## R2
- TC1250 XHTML: START -- Microsoft Word(.doc) -- START
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  END -- Microsoft Word(.doc) -- END

## R3
- TC1250 XHTML: START -- Microsoft Word(.docx) -- START
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  END -- Microsoft Word(.docx) -- END

## R4
- TC1250 XHTML: START -- Microsoft Excel(.xls) -- START
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  END -- Microsoft Excel(.xls) -- END

## R5
- TC1250 XHTML: START -- Microsoft Excel(.xlsx) -- START
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  END -- Microsoft Excel(.xlsx) -- END

## R6
- TC1250 XHTML: START -- Microsoft Powerpoint(.ppt) -- START
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  END -- Microsoft Powerpoint(.ppt) -- END

## R7
- TC1250 XHTML: START -- Microsoft Powerpoint(.pptx) -- START
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  END -- Microsoft Powerpoint(.pptx) -- END
