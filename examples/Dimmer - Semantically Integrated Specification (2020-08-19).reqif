# Dimmer - Semantically Integrated Specification (2020-08-19)
This specification method integrates and represents:
- processes, system composition and requirements (dynamic, static and detail views)
- mechanic, electric and software components with their interfaces.

It is important to understand, that all plans (diagrams) are views of a common system engineering model, sometimes called 'system repository'. Thus, consistency is always maintained.

The model elements are connected with relations, most of which are defined by positioning graph elements. For example, if a system component is drawn within another, a relationship 'contains' is created in the logic representation of the engineering model. Other relations, such as a system component 'satisfies' a requirement are created manually.  

Also, the documents are generated from the system engineering model. The ordering is in most projects (it can be rearranged, however, if appropriate):
- All plans
- A glossary with descriptions of all model elements appearing on one or more plans
- A hierarchically ordered list of requirements
- A list of open issues.
Please note that plans list related model elements and model elements list related requirements .. and vice versa. Active hyper-links are used, so that it is easy to jump between related model elements.

Further information is given in Appendix 'Method'.

# Specification: Dimmer - Semantically Integrated Specification (2020-08-19)
- ReqIF.Name: Dimmer - Semantically Integrated Specification (2020-08-19)
- ReqIF.Text: This specification method integrates and represents:
  - processes, system composition and requirements (dynamic, static and detail views)
  - mechanic, electric and software components with their interfaces.
  It is important to understand, that all plans (diagrams) are views of a common system engineering model, sometimes called 'system repository'. Thus, consistency is always maintained.
  The model elements are connected with relations, most of which are defined by positioning graph elements. For example, if a system component is drawn within another, a relationship 'contains' is created in the logic representation of the engineering model. Other relations, such as a system component 'satisfies' a requirement are created manually.
  Also, the documents are generated from the system engineering model. The ordering is in most projects (it can be rearranged, however, if appropriate):
  - All plans
  - A glossary with descriptions of all model elements appearing on one or more plans
  - A hierarchically ordered list of requirements
  - A list of open issues.
  Please note that plans list related model elements and model elements list related requirements .. and vice versa. Active hyper-links are used, so that it is easy to jump between related model elements.
  Further information is given in Appendix 'Method'.

## R1: Project Information (SpecIF:Heading)
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 Project Information
This is a small show-case illustrating the basic concepts for integrated mechatronic system specification. In addition to the original text and diagrams you will find logical relations between the information elements. Most relations are derived automatically from the diagrams; the resulting semantic net lends itself for navigation, search and audit.
The specification integrates and represents:
- processes, system composition and requirements (dynamic, static and detail views)
- mechanic, electric and software components with their interfaces.
It is important to understand, that all plans (diagrams) are views of a common system engineering model, sometimes called 'system repository'. Thus, consistency is always maintained.
The model elements are connected with relations, most of which are defined by positioning graph elements. For example, if a system component is drawn within another, a relationship 'contains' is created in the logic representation of the engineering model. Other relations, such as a system component 'satisfies' a requirement are created manually.
Also, the documents are generated from the system engineering model. The ordering is in most projects (it can be rearranged, however, if appropriate):
- All plans
- A glossary with descriptions of all model elements appearing on one or more plans
- A hierarchically ordered list of requirements
- A list of open issues.
Please note that plans list related model elements and model elements list related requirements .. and vice versa. Active hyper-links are used, so that it is easy to jump between related model elements.
Stakeholders:
| Name | Organisation | Telephone | Email |
| --- | --- | --- | --- |
| Vorname Nachname | Hersteller AG |  |  |
Legend:
To distinguish their type, element names are preceded by one of the following symbols:
| ▣ | Plan | A 'Diagram' is a graphical model view with a specific communication purpose, e.g. a business process or system composition. |
| --- | --- | --- |
| ■ | Actor (Role, Function) | An 'Actor' is a fundamental model element type representing an active entity, be it an activity, a process step, a function, a system component or a role. |
| ● | State (Information) | A 'State' is a fundamental model element type representing a passive entity, be it a value, a condition, an information storage or even a physical shape. |
| ♦ | Event | An 'Event' is a fundamental model element type representing a time reference, a change in condition/value or more generally a synchronisation primitive. |
| ✶ | Feature | A 'Feature' is an intentional distinguishing characteristic of a system, often a unique selling proposition. |
| ↯ | Requirement | A 'Requirement' is a singular documented physical and functional need that a particular design, product or process must be able to perform. |

## R2: System Composition (SpecIF:Heading)
.. showing the system and its composition of modules (at a higher level) and components (at a lower level). The relevant interfaces between the disciplines mechanical, electrical and software engineering are shown.

### R3: Color coding (SpecIF:Diagram)
- SpecIF:Diagram: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
- SpecIF:Notation: FMC Block Diagram
- Status: 40_approved
- HIS:SupplierStatus: not-applicable
- HIS:OemStatus: not-to-evaluate

### R4: SmartHome System (SpecIF:Diagram)
The Smart-Home-System consists of sensors on the left side, the controller in the middle and the actuators on the right side.
- SpecIF:Diagram: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
- SpecIF:Notation: FMC Block Diagram
- Status: 10_initial
- HIS:SupplierStatus: to-clarify
- HIS:OemStatus: to-evaluate
- SpecIF:shows -> R37
- SpecIF:shows -> R62
- SpecIF:shows -> R64
- SpecIF:shows -> R65
- SpecIF:shows -> R70
- SpecIF:shows -> R68
- SpecIF:shows -> R74
- SpecIF:shows -> R48
- SpecIF:shows -> R47
- SpecIF:shows -> R75
- SpecIF:shows -> R77
- SpecIF:shows -> R80
- SpecIF:shows -> R81
- SpecIF:shows -> R55

### R5: Flush-mounted Dimmer (SpecIF:Diagram)
.. showing the components of the device with their interfaces.
- SpecIF:Diagram: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
- SpecIF:Notation: FMC Block Diagram
- Status: 10_initial
- HIS:SupplierStatus: not-agreed
- HIS:OemStatus: not-accepted
- SpecIF:shows -> R60
- SpecIF:shows -> R34
- SpecIF:shows -> R61
- SpecIF:shows -> R40
- SpecIF:shows -> R41
- SpecIF:shows -> R62
- SpecIF:shows -> R64
- SpecIF:shows -> R66
- SpecIF:shows -> R69
- SpecIF:shows -> R71
- SpecIF:shows -> R76
- SpecIF:shows -> R78
- SpecIF:shows -> R81
- SpecIF:shows -> R58
- SpecIF:shows -> R82

### R6: Dimmer Module (SpecIF:Diagram)
- SpecIF:Diagram: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
- SpecIF:Notation: FMC Block Diagram
- Status: 10_initial
- HIS:SupplierStatus: partly-agreed
- HIS:OemStatus: to-evaluate
- SpecIF:shows -> R61
- SpecIF:shows -> R38
- SpecIF:shows -> R39
- SpecIF:shows -> R40
- SpecIF:shows -> R63
- SpecIF:shows -> R66
- SpecIF:shows -> R43
- SpecIF:shows -> R67
- SpecIF:shows -> R69
- SpecIF:shows -> R71
- SpecIF:shows -> R72
- SpecIF:shows -> R73
- SpecIF:shows -> R76
- SpecIF:shows -> R78
- SpecIF:shows -> R79

## R7: Scenarios (SpecIF:Heading)
.. showing the behavioral aspects of system design, both from external user perspective ('black box') and from internal perspective ('white box').

### R8: Dimming (SpecIF:Heading)

#### R9: User Activity (SpecIF:Diagram)
This shows the defined sequences of manual operation to activate the device.
- SpecIF:Diagram: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
- SpecIF:Notation: BPMN Process Model
- Status: 20_drafted
- HIS:SupplierStatus: agreed
- HIS:OemStatus: accepted
- SpecIF:shows -> R35
- SpecIF:shows -> R36
- SpecIF:shows -> R85
- SpecIF:shows -> R86
- SpecIF:shows -> R87
- SpecIF:shows -> R44
- SpecIF:shows -> R45
- SpecIF:shows -> R46
- SpecIF:shows -> R97
- SpecIF:shows -> R98
- SpecIF:shows -> R99
- SpecIF:shows -> R55

#### R10: Double-Button Observer Software (SpecIF:Diagram)
This software module discriminates the user's activity (operation sequence) and submits corresponding events/commands to the actuator. This software is generic with respect to the actuator, it can be used for [[dimmer]]s, [[shading]] devices and others.
- SpecIF:Diagram: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
- SpecIF:Notation: BPMN Process Model
- Status: 20_drafted
- HIS:SupplierStatus: agreed
- HIS:OemStatus: accepted
- SpecIF:shows -> R42
- SpecIF:shows -> R88
- SpecIF:shows -> R89
- SpecIF:shows -> R96
- SpecIF:shows -> R100
- SpecIF:shows -> R101
- SpecIF:shows -> R56
- SpecIF:shows -> R57

#### R11: Dimmer Controller Software (SpecIF:Diagram)
This software decodes the commands and controls the timely behavior of the actuator.
- SpecIF:Diagram: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
- SpecIF:Notation: Petri Net
- Status: 20_drafted
- HIS:SupplierStatus: agreed
- HIS:OemStatus: accepted
- SpecIF:shows -> R84
- SpecIF:shows -> R38
- SpecIF:shows -> R88
- SpecIF:shows -> R89
- SpecIF:shows -> R90
- SpecIF:shows -> R91
- SpecIF:shows -> R92
- SpecIF:shows -> R93
- SpecIF:shows -> R94
- SpecIF:shows -> R95
- SpecIF:shows -> R96
- SpecIF:shows -> R49
- SpecIF:shows -> R50
- SpecIF:shows -> R51
- SpecIF:shows -> R52
- SpecIF:shows -> R53
- SpecIF:shows -> R54
- SpecIF:shows -> R100
- SpecIF:shows -> R101

## R12: Requirements (SpecIF:Heading)

### R13: Function (SpecIF:Heading)
The requirements related to the product function.

#### REQ_014: Dim an electric load (IREB:Requirement)
The user can set the intensity level of an electric load such as a light [[bulb]]. Pressing a button 'up' or 'down', the intensity is increased or decreased following a quasi-stepless ramp.
- Status: 40_approved
- SpecIF:Priority: 2_medium
- Perspective: User
- Discipline: Mechanics, Electronics, Software
- HIS:SupplierStatus: agreed
- HIS:SupplierComment: Our solution does this perfectly.
- SpecIF:dependsOn -> REQ_015

#### REQ_016: Switch an electric load (IREB:Requirement)
The user can immediately switch 'on' or 'off' the electric load. The intensity set to the maximum resp. minimum level, as defined by installation parameters.
- Status: 40_approved
- SpecIF:Priority: 2_medium
- Perspective: User
- Discipline: Electronics, Software

#### REQ_015: Set dimming parameters (IREB:Requirement)
During system setup, the installer can modify the following parameters:
- maximum intensity
- minimum intensity
- dimming speed (intensity ramp when dimming)
- Status: 30_submitted
- SpecIF:Priority: 2_medium
- Perspective: User
- Discipline: Software

#### REQ_009: Minimum button size (IREB:Requirement)
The button size must not be less than 2 cm in diameter.
- Status: 40_approved
- SpecIF:Priority: 1_high
- Perspective: User
- Discipline: Mechanics
- HIS:SupplierStatus: to-clarify
- HIS:SupplierComment: We did not find the actual minimum dimensions of the buttons.

#### REQ_001: Electric load is 120 W (IREB:Requirement)
The power stage must allow an electric load of 120 W.
- Status: 30_submitted
- SpecIF:Priority: 1_high
- Perspective: User
- Discipline: Electronics
- HIS:SupplierStatus: to-clarify
- HIS:SupplierComment: For which time period?  Permanent load?

### R19: Quality (SpecIF:Heading)
The requirements related to quality characteristics of the product.

#### REQ_003: Instant use (IREB:Requirement)
85% of an arbitrarily selected group of test users understands and can use the system without reading a manual.
- Status: 40_approved
- SpecIF:Priority: 2_medium
- Perspective: User
- Discipline: Mechanics, Software
- HIS:SupplierStatus: agreed

#### REQ_008: Instantaneous reaction (IREB:Requirement)
The reaction time of the system to user input is 'instantaneous' (&lt; 0,5 sec).
- Status: 60_completed
- SpecIF:Priority: 1_high
- Perspective: User
- Discipline: Software
- HIS:SupplierStatus: agreed
- HIS:SupplierComment: Mais bien sûr.
- HIS:OemStatus: to-evaluate
- HIS:OemComment: Das ist ganz wichtig für uns.

#### REQ_011: Consistent system behavior (IREB:Requirement)
The system's behavior must be consistent. For example, controlling a dimmer must correspond with controlling a shade.
- Status: 40_approved
- SpecIF:Priority: 2_medium
- Perspective: User
- Discipline: Mechanics, Software

#### REQ_010: No dead-locks (IREB:Requirement)
Under no circumstances the system may get stuck in a dead-lock. I.e. every sequence of input stimulation must be supported, even arbitrary sequences. Input stimulation which is not supported in a given system state is either refused with an error message, if a feedback channel is available, or it is simply ignored, otherwise.
- Status: 40_approved
- SpecIF:Priority: 1_high
- Perspective: System
- Discipline: Electronics, Software
- SpecIF:dependsOn -> REQ_006

#### REQ_002: Overload protection (IREB:Requirement)
The dimmer unit is protected against resistive overload and against any capacitive or inductive loads.
- Status: 30_submitted
- SpecIF:Priority: 2_medium
- Perspective: User
- Discipline: Electronics

#### REQ_007: Auto shut-off (IREB:Requirement)
In case of over-temperature the device is shut-off automatically by an electronic circuit.
- Status: 30_submitted
- SpecIF:Priority: 2_medium
- Perspective: System
- Discipline: Electronics

### R26: Constraints (SpecIF:Heading)
The requirements related to constraints for product conception, such as regulations or technical choices made upfront.

#### REQ_012: Compliance with industry standards (IREB:Requirement)
The system must comply with industry standards. Besides legal and safety requirements, compatibility with existing electrical installations, tools and commercial components is desired.
- Status: 40_approved
- SpecIF:Priority: 2_medium
- Perspective: User
- Discipline: Mechanics, Electronics, Safety

#### REQ_004: Industry-standard mounting (IREB:Requirement)
The product fits into an industry-standard [[housing]] for flush-mounted devices (diameter &#x2300;68 mm). It is fixed with two screw-activated claws.
- Status: 30_submitted
- SpecIF:Priority: 1_high
- Perspective: System
- Discipline: Mechanics

#### REQ_005: Fire protection (IREB:Requirement)
The product must withstand 650°C (VDE 0606-1).
- Status: 30_submitted
- SpecIF:Priority: 1_high
- Perspective: User
- Discipline: Mechanics, Electronics

#### REQ_013: Galvanic Isolation (IREB:Requirement)
The load circuit with power stage is galvanically isolated from the controller.
- Status: 30_submitted
- SpecIF:Priority: 1_high
- Perspective: System
- Discipline: Electronics
- HIS:SupplierComment: This is standard for all our products: expensive, but effective.
- HIS:OemStatus: to-evaluate

#### REQ_006: Complete state-machine (IREB:Requirement)
The system is controlled by a complete state-machine and must not have any dead-lock state.
- Status: 40_approved
- SpecIF:Priority: 2_medium
- Perspective: System
- Discipline: Software

## R32: Model-Elements (Glossary) (SpecIF:Heading)

### R33: Type 'Actor' (SpecIF:Heading)
An 'Actor' is a fundamental model element type representing an active entity, be it an activity, a process step, a function, a system component or a role.

#### R34: Assembly Frame (FMC:Actor)
Mounting frame screwed to or into a wall.
- SpecIF:writes -> R76
- SpecIF:reads -> R76

#### R35: Briefly press Down-button (FMC:Actor)
Press down-button &lt;x ms.

#### R36: Briefly press Up-button (FMC:Actor)
Press up-button &lt;x ms.

#### R37: Bulb (FMC:Actor)
Dimmable candescent light-bulb 230V.
- SpecIF:reads -> R64

#### R38: Dimmer Controller Software (FMC:Actor)
Input commands (events):
- up-long → increase brightness
- down-long → decrease brightness
- release → stop dimming, keep brightness
- up-short → switch to maximum
- down-short → switch to minimum
- inappropriate commands are ignored (e.g. up-long when maximum is set).
- set parameters
Four parameters influence the behavior of the particular device:
- minimum value (default: 0%)
- maximum value (default: 100%)
- ramp-up speed (default: 10% per sec)
- ramp-down speed (default: 10% per sec)
- oslc_rm:satisfies -> REQ_014
- oslc_rm:satisfies -> REQ_016
- oslc_rm:satisfies -> REQ_015
- oslc_rm:satisfies -> REQ_006
- SpecIF:contains -> R88
- SpecIF:contains -> R89
- SpecIF:contains -> R91
- SpecIF:contains -> R92
- SpecIF:contains -> R93
- SpecIF:contains -> R94
- SpecIF:contains -> R95
- SpecIF:contains -> R96
- SpecIF:contains -> R53
- SpecIF:contains -> R54
- SpecIF:contains -> R100
- SpecIF:contains -> R101
- SpecIF:reads -> R67
- SpecIF:reads -> R73

#### R39: Dimmer Electronics (FMC:Actor)
The Dimmer Electronics is a printed circuit board with low-power micro-processor, memory, binary as well as analog I/O signals and a power stage supporting the specified electric load.
Diagramm:
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- oslc_rm:satisfies -> REQ_014
- oslc_rm:satisfies -> REQ_001
- oslc_rm:satisfies -> REQ_002
- oslc_rm:satisfies -> REQ_007
- oslc_rm:satisfies -> REQ_013
- SpecIF:writes -> R66
- SpecIF:reads -> R66
- SpecIF:writes -> R69
- SpecIF:reads -> R69
- SpecIF:writes -> R71
- SpecIF:reads -> R71
- SpecIF:writes -> R78
- SpecIF:reads -> R78
- SpecIF:writes -> R73
- SpecIF:writes -> R67
- SpecIF:reads -> R61
- SpecIF:reads -> R79
- SpecIF:reads -> R63
- SpecIF:reads -> R72

#### R40: Dimmer Module (FMC:Actor)
The actuator module with dimmer function for resistive loads.
- oslc_rm:satisfies -> REQ_014
- oslc_rm:satisfies -> REQ_008
- oslc_rm:satisfies -> REQ_011
- oslc_rm:satisfies -> REQ_012
- oslc_rm:satisfies -> REQ_005
- SpecIF:contains -> R38
- SpecIF:contains -> R39
- SpecIF:contains -> R43
- SpecIF:contains -> R63
- SpecIF:contains -> R73
- SpecIF:contains -> R67
- SpecIF:contains -> R72
- SpecIF:contains -> R79
- SpecIF:reads -> R61

#### R41: Double Button (FMC:Actor)
The Double Button (a sensor unit) is a versatile all-mechanical unit used for multiple purposes. The mechanical position is transferred with a rod per button to the next unit where it is converted to an electrical signal.
- oslc_rm:satisfies -> REQ_009
- SpecIF:writes -> R76
- SpecIF:reads -> R76
- SpecIF:writes -> R60
- SpecIF:reads -> R62
- SpecIF:reads -> R81

#### R42: Double-Button Observer Software (FMC:Actor)
This is an observer of the double-button sensor. It distinguishes short and long pressing in the 'up' and 'down' directions. A discriminator may send five events:
- up-short
- down-short
- up-long
- down-long and
- release.
The events are interpreted and actions are initiated accordingly by the target actuator unit. The double button sensor and the observer have no notion of the underlying function.
- SpecIF:contains -> R88
- SpecIF:contains -> R89
- SpecIF:contains -> R96
- SpecIF:contains -> R100
- SpecIF:contains -> R101
- SpecIF:contains -> R56
- SpecIF:contains -> R57

#### R43: Housing (FMC:Actor)
Diagramm:
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- SpecIF:writes -> R76
- SpecIF:reads -> R76
- SpecIF:writes -> R63
- SpecIF:writes -> R72
- SpecIF:writes -> R79

#### R44: Press and hold Down-button (FMC:Actor)
Press down-button &gt;x ms.

#### R45: Press and hold Up-button (FMC:Actor)
Press up-button &gt;x ms.

#### R46: Release button (FMC:Actor)

#### R47: Shading (FMC:Actor)
Window-shade with 2 degrees of freedom: It can be moved up/down and the elements can be set straight/tilted. Both movements can be made proportionally with an electric drive.
- SpecIF:reads -> R68

#### R48: SmartHome Controller (FMC:Actor)
The controller
- interconnects locally distributed sensors and actuators,
- coordinates different actuators where appropriate and
- performes automatic functions, such as switching external lamps dependend on ambient light.
- oslc_rm:satisfies -> REQ_010
- SpecIF:writes -> R64
- SpecIF:reads -> R64
- SpecIF:writes -> R68
- SpecIF:reads -> R65
- SpecIF:reads -> R74

#### R49: Start-decreasing (FMC:Actor)

#### R50: Start-increasing (FMC:Actor)

#### R51: Stop-decreasing (FMC:Actor)

#### R52: Stop-increasing (FMC:Actor)

#### R53: Switch-off (FMC:Actor)
Switch to programmed min-value.

#### R54: Switch-on (FMC:Actor)
Switch to programmed max-value.

#### R55: User (FMC:Actor)
- oslc_rm:satisfies -> REQ_003
- SpecIF:contains -> R35
- SpecIF:contains -> R36
- SpecIF:contains -> R44
- SpecIF:contains -> R45
- SpecIF:contains -> R46
- SpecIF:contains -> R85
- SpecIF:contains -> R86
- SpecIF:contains -> R87
- SpecIF:contains -> R97
- SpecIF:contains -> R99
- SpecIF:contains -> R98
- SpecIF:writes -> R74
- SpecIF:writes -> R65
- SpecIF:writes -> R64

#### R56: Wait for Activation (FMC:Actor)
The kind of activation is determined:
- Up- or Down-Button
- Short or long activation: 'Short' is &lt; 0,4 sec.
- Do only wait until the distinction between 'short' or 'long' can be made!

#### R57: Wait for Deactivation (FMC:Actor)

#### R58: Wireless Module (FMC:Actor)
Receives control commands via radio signal or the mechanical position of a mounted sensor unit. Sends electrical control signals to the mounted actuator module.
- oslc_rm:satisfies -> REQ_008
- SpecIF:writes -> R76
- SpecIF:reads -> R76
- SpecIF:writes -> R82
- SpecIF:reads -> R82
- SpecIF:writes -> R61
- SpecIF:reads -> R60

### R59: Type 'State' (SpecIF:Heading)
A 'State' is a fundamental model element type representing a passive entity, be it a value, a condition, an information storage or even a physical shape.

#### R60: Actuator Rods (FMC:State)
Up to four actuator rods connecting the buttons to electrical contacts.

#### R61: Control Signals (FMC:State)

#### R62: down (FMC:State)
The button to drive down the dimmer, shading or similar devices.

#### R63: Electro-Magnetic Resistance (FMC:State)
Electromagnetic characteristics, especially EM-shielding.

#### R64: Flush-mounted Dimmer (FMC:State)
A dimmer for electric loads in an industry-standard mounting frame which is flush with the wall surface. In other words, the dimmer is sitting in the wall and just the buttons are visible.
- oslc_rm:satisfies -> REQ_010
- oslc_rm:satisfies -> REQ_004
- oslc_rm:satisfies -> REQ_005
- SpecIF:contains -> R34
- SpecIF:contains -> R40
- SpecIF:contains -> R41
- SpecIF:contains -> R58
- SpecIF:contains -> R60
- SpecIF:contains -> R61
- SpecIF:contains -> R62
- SpecIF:contains -> R81
- SpecIF:contains -> R76

#### R65: Flush-mounted Shading Control (FMC:State)
- oslc_rm:satisfies -> REQ_010
- oslc_rm:satisfies -> REQ_004
- SpecIF:contains -> R62
- SpecIF:contains -> R81
- SpecIF:contains -> R77
- SpecIF:contains -> R80

#### R66: Ground Cable (FMC:State)
- Cable-diameter
- Wire-diameter
- Max-current

#### R67: I/O Pins (FMC:State)
per input and output signal:
- hardware-address
- number of significant bits

#### R68: Intelligent Shading Drive (FMC:State)
An intelligent shading actuator with 2 drives for up/down straight/tilt motion. The unit comprises the control unit and the motors.
- oslc_rm:satisfies -> REQ_010
- oslc_rm:satisfies -> REQ_002
- oslc_rm:satisfies -> REQ_007
- oslc_rm:satisfies -> REQ_005
- SpecIF:contains -> R70

#### R69: Load Cable (FMC:State)
- Cable-diameter
- Wire-diameter
- Max-current

#### R70: M (FMC:State)
Actuator Motor 230V.

#### R71: Neutral Cable (FMC:State)
- Cable-diameter
- Wire-diameter
- Max-current

#### R72: Physical Space (FMC:State)
Effective 3D interior space and mounting for electronics.

#### R73: Processor RAM ROM (FMC:State)
EPROM-Size
RAM-Size
Processor type with instruction set and speed (MIPS)

#### R74: Remote Control (FMC:State)
- SpecIF:contains -> R62
- SpecIF:contains -> R81

#### R75: SmartHome System (FMC:State)
The new system for controlling all major functions of the private home:
- light/illumination
- window shades
- heating
- consumption meters for electricity, heat, gas and water.
- oslc_rm:satisfies -> REQ_011
- oslc_rm:satisfies -> REQ_012
- SpecIF:contains -> R48
- SpecIF:contains -> R64
- SpecIF:contains -> R65
- SpecIF:contains -> R68
- SpecIF:contains -> R74

#### R76: Spring Clips (FMC:State)
Spring clips for mechanical connection.

#### R77: straighten (FMC:State)
The button to straighten the shading elements.

#### R78: Supply Cable (FMC:State)
- Cable-diameter
- Wire-diameter
- Max-current

#### R79: Thermal Resistance (FMC:State)
Thermal resistance and thermal capacity of the [[housing]].

#### R80: tilt (FMC:State)
The button to tilt the shading elements.

#### R81: up (FMC:State)
The button to drive up the dimmer, shading or similar devices.

#### R82: Wireless Network (FMC:State)

### R83: Type 'Event' (SpecIF:Heading)
An 'Event' is a fundamental model element type representing a time reference, a change in condition/value or more generally a synchronisation primitive.

#### R84: Decreasing (FMC:Event)

#### R85: Dim-down! (FMC:Event)

#### R86: Dim-up! (FMC:Event)

#### R87: Done! (FMC:Event)

#### R88: down-long! (FMC:Event)

#### R89: down-short! (FMC:Event)

#### R90: Increasing (FMC:Event)

#### R91: Intermediate (FMC:Event)

#### R92: max-reached! (FMC:Event)

#### R93: Maximum (FMC:Event)

#### R94: min-reached! (FMC:Event)

#### R95: Minimum (FMC:Event)

#### R96: released! (FMC:Event)

#### R97: Stop dimming! (FMC:Event)

#### R98: Switch-off! (FMC:Event)

#### R99: Switch-on! (FMC:Event)

#### R100: up-long! (FMC:Event)

#### R101: up-short! (FMC:Event)

## R102: Parts List (SpecIF:Heading)
This Parts List has been automatically generated from the model.

## R103: Open Issues (SpecIF:Heading)

### R104: Mechanical (SpecIF:Heading)

#### OPM_001: An open issue with respect to mechanics (SpecIF:Issue)
This is the description of the issue and potential solution.
- SpecIF:Priority: 3_low
- SpecIF:DueDate: 2012-09-30T12:00:00+02:00
- SpecIF:refersTo -> REQ_016
- SpecIF:refersTo -> REQ_003
- SpecIF:refersTo -> R43

### R106: Software (SpecIF:Heading)

#### OPS_001: An open issue concerning software (SpecIF:Issue)
A description.
- SpecIF:Priority: 2_medium
- SpecIF:Responsible: Vorname Nachname
- SpecIF:DueDate: 2012-09-30T12:00:00+02:00
- SpecIF:refersTo -> R74
