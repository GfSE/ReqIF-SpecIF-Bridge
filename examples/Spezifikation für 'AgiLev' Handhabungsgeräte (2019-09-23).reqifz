# Spezifikation für 'AgiLev' Handhabungsgeräte (2019-09-23)

# Specification: Spezifikation für 'AgiLev' Handhabungsgeräte (2019-09-23)
- ReqIF.Name: Spezifikation für 'AgiLev' Handhabungsgeräte (2019-09-23)

## R1: Projektinformation (Ordner)
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Projektbeteiligte:
| Name | Organisation | Telefon | Email |
| --- | --- | --- | --- |
| Armin Seidenrock |  |  | as@agilev.de |
| Dr. Norbert Baumgart |  |  | nb@agilev.de |
| Dr. Oskar v. Dungern | enso managers GmbH |  | od@enso-managers.com |
Legende:
Zur Unterscheidung ihres Typs ist den Elementnamen eines der folgenden Symbole vorangestellt:
| ▣ | Plan | Ein 'Plan' ist ein Modelldiagramm zur Vermittlung eines bestimmten Sachverhalts, z.B. ein Geschäftsprozess oder Systemaufbau. |
| --- | --- | --- |
| ■ | Akteur (Rolle, Funktion) | Ein 'Akteur' ist ein fundamentaler Modellelement-Typ für ein aktives Objekt, z.B. eine Aktivität, ein Prozess-Schritt, eine Funktion, eine Systemkomponente oder eine Rolle. |
| ● | Zustand (Information) | Ein 'Zustand' ist ein fundamentaler Modellelement-Typ für ein passives Objekt, z.B. ein Wert, eine Bedingung, ein Informationsspeicher oder eine physische Beschaffenheit. |
| ♦ | Ereignis | Ein 'Ereignis' ist ein fundamentaler Modellelement-Typ für eine zeitliche Referenz, eine Änderung einer Bedingung bzw. eines Zustandes oder generell ein Synchronisations-Mittel. |
| ✶ | Produktmerkmal | Ein 'Ausstattungsmerkmal' ist eine beabsichtigte differenzierende Eigenschaft eines Systems, oft ein Alleinstellungsmerkmal. |
| ↯ | Anforderung | Eine 'Anforderung' ist ein einzelnes dokumentiertes physisches oder funktionales Bedürfnis, das der betreffende Entwurf, das Produkt oder der Prozess erfüllen muss. |

## R2: Aktive Magnetlagerung (Ordner)

### R3: Prinzip des magnetischen Linearlagers (Plan)
- Bewegungsrichtung des [[Schlitten]]s ist senkrecht zur Bildebene.
- Das Magnetlager bestimmt 5 räumliche Freiheitsgrade, während der 6. Freiheitsgrad der Bewegungsachse entspricht und vom Antrieb gesteuert wird.
- Gezeigte Anordnung der Magnete jeweils am vorderen und hinteren Rand des Schlittens.
- Das Spaltmaß zwischen jedem [[Elektro-Magnet]]en und dem [[Schlitten]] wird gemessen und für die Berechnung des Positions-Istwertes in 2 translatorischen und 3 rotatorischen Freiheitsgraden herangezogen.
Modellsicht:
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- zeigt -> R47
- zeigt -> R58

### R4: Lageregelung (Plan)
Die Lage des [[Schlitten]]s in 2 translatorischen Freiheitsgraden senkrecht zur Bewegungsachse sowie in den 3 rotatorischen Freiheitsgraden wird geregelt.
- Als Sensoren stehen 6 analoge Positions-Sensoren und bis zu 4 [[Beschleunigungs-Sensor]]en zur Verfügung.
- Als Stellglieder wirken 4 senkrecht wirkende und 2 horizontal wirkende [[Elektro-Magnet]]e.
Modellsicht:
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- zeigt -> R66
- zeigt -> R45
- zeigt -> R47
- zeigt -> R75
- zeigt -> R52
- zeigt -> R54
- zeigt -> R58
- zeigt -> R79
- zeigt -> R62
- zeigt -> R63

### R5: Elektronik-Baugruppen (Ordner)

#### R6: Verteiler und Magnetlager-Steuerung (Plan)
Modellsicht:
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- zeigt -> R44
- zeigt -> R66
- zeigt -> R45
- zeigt -> R68
- zeigt -> R69
- zeigt -> R46
- zeigt -> R70
- zeigt -> R71
- zeigt -> R47
- zeigt -> R48
- zeigt -> R49
- zeigt -> R72
- zeigt -> R50
- zeigt -> R74
- zeigt -> R51
- zeigt -> R75
- zeigt -> R53
- zeigt -> R54
- zeigt -> R56
- zeigt -> R57
- zeigt -> R76
- zeigt -> R77
- zeigt -> R78
- zeigt -> R59
- zeigt -> R60
- zeigt -> R61
- zeigt -> R79
- zeigt -> R80
- zeigt -> R64
- zeigt -> R83

#### R7: Magnetlager-Steuerung mit Einzelprozessor (Plan)
Die zukünftige Lösung mit 1 DSP auf der Prozessorplatine.
Modellsicht:
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- zeigt -> R67
- zeigt -> R69
- zeigt -> R71
- zeigt -> R50
- zeigt -> R73
- zeigt -> R51
- zeigt -> R55
- zeigt -> R57
- zeigt -> R76
- zeigt -> R77
- zeigt -> R80
- zeigt -> R81
- zeigt -> R82

### R8: Mechanischer Aufbau der x-Achse (Ordner)
An den vier Ecken des [[Schlitten]]s sind die vertikal angeordneten Hubmagneten zu sehen, die im statischen Lastfall die Schwerkraft kompensieren. Im unteren Bereich des Schlittens sind weiterhin die zwei [[Elektro-Magnet]]e angeordnet, die ein statisches Gleichgewicht mit den gegenüber liegenden Permanent-Magneten in horizontaler Richtung bilden.
In der Wirkrichtung der Elektro-Magneten sind die Positions-Sensoren angeordnet, die ein analoges Signal proportional zum Spaltmaß liefern.
Im dynamischen Lastfall stabilisieren die Elektro-Magneten die relative Position des Schlittens auch bei Störeinflüssen. Neben der Dämpfung eingeleiteter Kräfte und Momente wird die Steifheit des Lagers signifikant verbessert.
Die heutige [[Magnetlager-Steuerung]] ist auf dem Diagramm als blau eingefärbte Platine zu erkennen. Die neu zu entwickelnde Elektronik für die Magnetlager-Steuerung soll ebendort unter gebracht werden. Der grau eingezeichnete Quader belegt den Platz für ein Endeffektor-Netzteil. Es verbleibt etwas Platz auf der Grundfläche, der für die Verteilerplatine genutzt werden kann.
Der Bauraum ist in einer Anforderung bemaßt.
Diagramm
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
### R9: Anforderungen an die Elektronik für aktive Magnetlager (Ordner)

#### EL_009: Modularer Aufbau (IREB:Requirement)
Status: 40_approved, Prio: 2_medium
Die neue Magnetlagersteuerung, auch genannt ‚Active Magnetic Bearing‘ Controller (AMB), soll modular aufgebaut sein:
- Platine A (Prozessorplatine): Digitalteil mit einem Mikroproozessor (DSP).
- Platine B (Verstärkerplatine): Die Endstufen für die Ansteuerung von 6 Hubmagneten.
Die Prozessorplatine soll im Normalfall eine Verstärkerplatine oder im Sonderfall zwei Verstärkerplatinen ansteuern können.
- Status: 40_approved
- Priorität: 2_medium

#### EL_022: Induktive Last (IREB:Requirement)
Status: 40_approved, Prio: 1_high
Jede Last wird mit 48 V und max. 5A Dauerstrom in beiden Polaritäten betrieben. Ein kurzzeitiger Spitzenstrom kann 7A betragen.
- Die Induktivität der Last kann je nach Ausführung des Hubmagneten 5mH bis 250mH betragen.
- Der ohmsche Widerstand der Last kann je nach Ausführung im Bereich von 0,5 bis 3 Ohm liegen.
- Jede Last wird über einen eigenen Steckverbinder mit Berührschutz und Verriegelung angeschlossen.
- Status: 40_approved
- Priorität: 1_high

#### EL_001: Last ist stromlos beim Einschalten (IREB:Requirement)
Status: 40_approved, Prio: 1_high
Die Last ist nach dem Einschalten stromlos. Alle Schalter der Endstufe sind offen. Die Lageregelung wird durch die Software angefahren.
- Status: 40_approved
- Priorität: 1_high

#### EL_002: Die Endstufe kann komplett abgeschaltet werden. (IREB:Requirement)
Status: 40_approved, Prio: 1_high
Per Software können alle Schalter der Endstufe geöffnet werden.
- Status: 40_approved
- Priorität: 1_high

#### EL_014: Externe Freigabe (IREB:Requirement)
Status: 40_approved, Prio: 1_high
Ein externes Binärsignal erlaubt es die Endstufe freizugeben ("Enable") bzw. unabhängig von der Ansteuerung eines Prozessors alle Schalter zu öffnen. Ohne Beschaltung des Freigabe-Signals (default) sind alle Schalter der Endstufe geöffnet.
- Status: 40_approved
- Priorität: 1_high

#### EL_018: Betriebsart (IREB:Requirement)
Status: 40_approved, Prio: 1_high
Im Betrieb wird die induktive Last mit einem pulsweiten-modulierten Signal (PWM) mit mindestens 20 kHz gesteuert. In der Neutralstellung (Aktuator leitet keine Kraft auf den lagegeregelten Körper ein), wird die Spannungsquelle im Tastverhältnis 50:50 in der einen und in der anderen Richtung an die Last angelegt. Durch Verändern des Tastverhältnisses wird ein ein positiver oder negativer effektiver Laststrom hervor gerufen.
- Status: 40_approved
- Priorität: 1_high
- Kommentar: Zu klären: Bevorzugt wird eine Ansteuerung aus dem Prozessor mit einem einzelnen PWM-Signal pro Endstufe; viele Prozessoren können jedoch auch paarweise ein nicht-invertiertes und invertiertes PWM-Signal liefern, bei dem jeweils das Einschalten leicht gegenüber dem Ausschalten verzögerrt ist, um Kurzschlüsse in der Endstufe zu vermeiden.

#### EL_007: Temperatur der Endstufe wird gemessen (IREB:Requirement)
Status: 40_approved, Prio: 2_medium
Bei den Endstufen soll ein Temperatursensor mit Messbereich bis 120°C angebracht werden. Der Temperatursensor soll über einen SPI Bus an den Prozessor angeschlossen werden. (Der Sensor wird nicht für den Schutz gegen Übertemperatur verwendet.)
- Status: 40_approved
- Priorität: 2_medium

#### EL_004: Schutz gegen Überstrom (IREB:Requirement)
Status: 40_approved, Prio: 1_high
Alle Schalter einer Endstufe werden über eine geeignete elektronische Schaltung geöffnet, wenn der Strom aus der Quelle den Maximalwert von 7A überschreitet. Dieser Zustand kann durch die Software per Binäreingang erkannt und über einen Binärausgang zurück gesetzt werden.
- Status: 40_approved
- Priorität: 1_high
- Kommentar: Auch möglich, dass sich die Funktion nach definierter Zeit (1s) selbst zurück setzt. --> Das wollen wir allerdings nicht: Wenn etwas schief geht, muss die übergeordnete Robotersteuerung entscheiden, wie weiter zu verfahren ist. (So sind z.B. auch Elmo und Copley Antriebe implementiert).

#### EL_005: Schutz gegen Übertemperatur (IREB:Requirement)
Status: 40_approved, Prio: 1_high
Alle Schalter einer Endstufe werden über eine geeignete elektronische Schaltung geöffnet, wenn die Temperatur des Kühlkörpers einen Maximalwert überschreitet. Dieser Zustand kann durch die Software per Binäreingang erkannt und über einen Binärausgang zurück gesetzt werden.
- Status: 40_approved
- Priorität: 1_high
- ist abhängig von -> EL_007

#### EL_017: Schutz gegen Induktion (IREB:Requirement)
Status: 40_approved, Prio: 1_high
Das lage-geregelte mechanische Bauteil ist einer hochdynamischen Krafteinwirkung ausgesetzt. Daher kann es zu erheblicher Induktion in der Last kommen. Die Elektronik und die Spannungsversorgung darf hierdurch nicht beschädigt werden.
- Status: 40_approved
- Priorität: 1_high

#### EL_013: Strom-Messung (IREB:Requirement)
Status: 40_approved, Prio: 1_high
Der Effektivwert des Stroms durch die Last in jeder der 6 Leistungsendstufen wird gemessen und dem Prozessor zugeführt. Der Messbereich beträgt +/-5,3 A; die AD-Wandlung im Prozessor erfolgt mit 12 Bit Auflösung.
Es ist auf eine rauscharme Strom-Messung zu achten.
- Status: 40_approved
- Priorität: 1_high
- Kommentar: Der angegebene Messbereich entspricht dem derzeitigen Stromsensor Allegro ACS712, dessen Messbereich in Interval von -5 bis 5 A linear ist.

#### EL_038: Positions-Messung mit Balluff (IREB:Requirement)
Status: 40_approved, Prio: 2_medium
Im Falle der atm. X-Achse kommen 6 Positions-Sensoren Balluff BAW000J zum Einsatz. Jeder Anschluss besteht aus:
- Versorung (24V)
- Analoges Mess-Signal im Bereich 0-10 V.
- GND
Näheres unter http://www.balluff.com.
- Status: 40_approved
- Priorität: 2_medium

#### EL_039: Positions-Messung mit Hall-Sensor (IREB:Requirement)
Status: 30_submitted, Prio: 2_medium
Für Achsen im Vakuum kommt ein doppelter Hallsensor mit programmierbarer Kennlinien-Linearisierung zum Einsatz. Die Anschlüsse sind:
- Versorgung 5V
- differentielles Mess-Signal im Bereich 0..5V (0..3,3 V?)
- GND.
- Status: 30_submitted
- Priorität: 2_medium

#### EL_040: Positionsmessung mit kapazitivem Sensor (IREB:Requirement)
Status: 30_submitted, Prio: 3_low
Einsatz von kapazitiven Sensoren für die Messung des Luftspalts (Lagemessung) im Vakuum. Eine spezielle Elektronik zur Signalaufbereitung ist erforderlich. Näheres unter http://www.micro-epsilon.de.
- Status: 30_submitted
- Priorität: 3_low

#### EL_034: Beschleunigungs-Messung (IREB:Requirement)
Status: 30_submitted, Prio: 2_medium
Um die Beschleunigung der mechanischen Strecke zusätzlich zur Lage an verschiedenen Stellen messen zu können, können Beschleunigungsaufnehmer eingesetzt werden. Als Zubehör für Arduino findet man fertig bestückte Adapterplatinen, auf denen ein ADXL335 von Analog Devices verbaut ist. Da diese Platinen auch in der Ausführung mit integriertem Festspannungsregler erhältlich sind, können sie wahlweise mit 5V oder 3,3V versorgt werden. Die Beschleunigung kann damit in drei Raumrichtungen als Analogsignal erfasst und dem Prozessor zugeführt werden.
- Status: 30_submitted
- Priorität: 2_medium

#### EL_011: Analoge Sensor-Schnittstellen (IREB:Requirement)
Status: 40_approved, Prio: 1_high
Die Prozessorplatine weist 10 Sensor-Schnittstellen auf, die als Analogsignal auf A/D-Wandler des Prozessors geführt werden. Jeder Anschluss besteht aus:
- 5V Versorgung
- zwei differenzielle Eingänge mit dem Messbereich 0-3,3 V
- GND
Jede Sensorschnittstelle kann wahlweise für Positions- oder Beschleunigungssensoren verwendet werden.
- Status: 40_approved
- Priorität: 1_high
- Kommentar: Zu klären, ob es einen einzelnen Stecker für alle Sensorsignale gibt, der zu einer achs-spezifischen Platine zur Anpassung der Sensorsignale führt, oder ob es getrennte, universelle Stecker für jedes Sensorsignal gibt, so dass verschiedene Sensoren angeschlossen werden können.

#### EL_012: Binäre Schnittstellen (IREB:Requirement)
Status: 40_approved, Prio: 2_medium
Die Prozessorplatine weist eine doppelreihige Steckpfostenleiste für Binärsignale auf. Die Signale werden unmittelbar auf den Prozessor geführt; durch geeignete Programmierung ist jedes Signal als Eingang oder Ausgang verwendbar. Der Stecker soll auch Zugang zu verfügbaren Bussen bieten, z.B. SPI, UART. Die Anzahl der Signale wird nach Auswahl des Prozessors festgelegt.
- Status: 40_approved
- Priorität: 2_medium

#### EL_016: CAN-Bus (IREB:Requirement)
Status: 40_approved, Prio: 1_high
Die Prozessorplatine weist einen 1x4 Steckpfostenverbinder zum Anschluss eines CAN-Buskabels auf. Im gleichen Anschluss wird ein weiterer Pin für den Prozessorstatus (Störzustand) verwendet; der Pin ist an einem als Ausgang konfigurierten Binärsignal (GPIO) des Prozessors angeschlossen.
- Status: 40_approved
- Priorität: 1_high

#### EL_029: CAN Transmitter mittels WLAN2CAN (IREB:Requirement)
Status: 40_approved, Prio: 3_low
Aktuell ist das 'Wireless CAN' mit Modulen vom Typ avisaro 20511 (http://www.avisaro.com/tl/avisaro-wlan-modul-20.html) realisiert.
- Status: 40_approved
- Priorität: 3_low

#### EL_019: Optische Indikatoren (IREB:Requirement)
Status: 40_approved, Prio: 2_medium
Die Prozessorplatine ist mit 2 kleinen Leuchtdioden ausgestattet:
- 'Spannungsversorgung ein'
- plus eine angesteuert von einem Binärausgang des Prozessors.
- Status: 40_approved
- Priorität: 2_medium

#### EL_010: Kühlung der Endstufe (IREB:Requirement)
Status: 40_approved, Prio: 1_high
Die Leistungsendstufe ist mit einem Kühlkörper versehen. Die Umgebungstemperatur beträgt bis 40 °C. Für bis zu 2 sec kann die Elektronik in eine Wärmekammer von 80 °C eingefahren werden, wobei dieser Zustand nicht mehr als 10% der Gesamtzeit ausmacht.
Der Kühlkörper ist im Bauraum oben (am „Dach“) angeordnet.
- Status: 40_approved
- Priorität: 1_high
- Kommentar: Die Kühlung im Vakuum ist noch zu klären.

#### EL_023: Externe Spannungsversorgung (IREB:Requirement)
Status: 40_approved, Prio: 1_high
Die externe Spannungsversorgung beträgt 48V. Die Zuleitung weist einen Widerstand von bis zu 1 Ohm auf.
- Status: 40_approved
- Priorität: 1_high

#### EL_037: Dimensionierung der Spannungsversorgung (IREB:Requirement)
Status: 40_approved, Prio: 1_high
Die Leistung der Spannungswandler ist entsprechend folgender Tabelle auszulegen. Demnach werden benötigt:
- 24V / 16W
- 5V / 4W
- 3,3V / 4W
Anhang
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- Status: 40_approved
- Priorität: 1_high

#### EL_008: Versorgung für Elektronik ist zu gewinnen (IREB:Requirement)
Status: 40_approved, Prio: 1_high
Von extern wird nur die Spannung für die Last zugeführt. Die Versorgung für die Analog- und Digitalektronik ist daraus selbst zu gewinnen.
- Status: 40_approved
- Priorität: 1_high

#### EL_024: CAN Teststecker (IREB:Requirement)
Status: 40_approved, Prio: 2_medium
Die Platine weist einen 3-poligen Stecker für den CAN-Bus auf, um Tests auch dann durchführen zu können, wenn der CAN-Transmitter nicht bestückt ist.
- Status: 40_approved
- Priorität: 2_medium

#### EL_027: Programmierstecker (IREB:Requirement)
Status: 40_approved, Prio: 1_high
Für jeden Prozessor gibt es einen JTAG Programmierstecker. Die Bauform ergibt sich aus dem auszuwählenden Entwicklungssystem für den Prozessor.
- Status: 40_approved
- Priorität: 1_high

#### EL_026: Verpolungssichere Stecker im Rastemaß 2.54 (IREB:Requirement)
Status: 40_approved, Prio: 2_medium
Alle Steckverbinder sind durch ein geeignetes Gehäuse verpolungssicher. Das Rastermaß beträgt 2,54mm.
- Status: 40_approved
- Priorität: 2_medium

#### EL_028: Spannungswandler sind galvanisch entkoppelt (IREB:Requirement)
Status: 30_submitted, Prio: 2_medium
Zur Vermeidung von Massestörungen haben die einzelnen Spannungen eine getrennte Masse. Die Masseverbindung wird an der Last hergestellt.
- Status: 30_submitted
- Priorität: 2_medium
- Kommentar: Achtung: Es gibt sowohl die Motoransteuerung auf der Verteiler-Platine, als auch die 6 Endstufen auf der Magnetlager-Platine. Zu klären: Wie wird die Masseführung der Einheit aus Verteiler (Motorsteuerung und Magnetlager-Steuerung realisiert ?  Ist es ggf sinnvoll eine gemeinsame Masse für alle kleineren Spannungen vorzusehen (also Wandlung 48->24 isoliert, sowie 24->5 und 24->3,3 mit gemeinsamer Masse), um den Aufwand zu begrenzen?

#### EL_030: Vakuumtauglichkeit (IREB:Requirement)
Status: 30_submitted, Prio: 3_low
Die Elektronik kann in einem Ultra-Hoch-Vakuum (100 nPa) ohne Schäden betrieben werden.
- Status: 30_submitted
- Priorität: 3_low
- Kommentar: Die Vakuumtauglichkeit kann in einem späteren Entwicklungsschritt erreicht werden. Eventuell kann sie durch Vergiessen erreicht werden. Die Wärmeabfuhr ist noch zu klären.

#### EL_025: Bauraum für die Elektronik der X-Achse (IREB:Requirement)
Status: 40_approved, Prio: 2_medium
Im Falle der X-Achse ist der Bauraum für die Magnetlager-Steuerung kubisch; er hat eine Grundfläche von 129x215mm und eine maximale Höhe von 47mm. Ein Einschnitt für ein Endeffektor-Netzteil beträgt 120x60mm.
- Die Bewegungsrichtung der Achse ist parallel zur längsten Kante.
- Bohrungen zur Befestigung können an beliebiger Stelle in der Grundfläche platziert werden.
- Bei der X-Achse besteht der Magnetlager-Controller aus einer Prozessor- und einer Verstärkerplatine.
- Die in der Zeichnung sichtbare Haube verdeutlicht die Begrenzung des Bauraums (somit steht in der Mitte eine größere Höhe von bis zu 58mm zur Verfügung, sofern erforderlich); für den Kühlkörper wird sie mit einer Aussparung versehen.
Anhang
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- Status: 40_approved
- Priorität: 2_medium

#### EL_035: Elektrostatischer Greifer (IREB:Requirement)
Status: 30_submitted, Prio: 2_medium
Zur Versorgung des elektrostatischen Greifers kommt eine schaltbare Spannungsversorgung als Zubehör von dem Hersteller der elektrostatischen Beschichtung zum Einsatz. Die Spannungsquelle erzeugt Hochspannungen von etwa 1,2kV abhängig von der Versorgungsspannung um 24V (gemessene Stromspitzen bis 1A, dann 0).
Die Ansteuerung der Hochspannungsversorgung erfolgt über einen Digitalausgang des Elmo Antriebsreglers.
- Status: 30_submitted
- Priorität: 2_medium

#### EL_036: Vakuumgreifer (IREB:Requirement)
Status: 30_submitted, Prio: 2_medium
Der Vakuumgreifer verfügt über eine dezentrale Vakuumpumpe, die auf der X-Achse des Roboters montiert wird. Eingesetzt wird die XavItech V200Gas mit der Versorgungsspannung 3.2 bis 26V DC bei dem mittleren Strom 40-90mA. Die Pumpe besitzt eine integrierte Schaltung und verfügt über einen Schalteingang (GND/3.3V oder Vcc?).
- Status: 30_submitted
- Priorität: 2_medium

## R42: Modellelemente (Glossar) (Ordner)

### R43: Typ 'Akteur' (Ordner)
Ein 'Akteur' ist ein fundamentaler Modellelement-Typ für ein aktives Objekt, z.B. eine Aktivität, ein Prozess-Schritt, eine Funktion, eine Systemkomponente oder eine Rolle.

#### R44: Antriebs-Steuerung (Akteur (Rolle, Funktion))
Integriertes Standard-Modul Typ "Gold Whistle" der Firma ELMO mit 1,6kW Dauerleistung und 3,2kW kurzzeitiger Spitzenleistung. Es wird über CANopen angesteuert. Neben der Motorsteuerung gibt es einige optisch isolierte Schaltausgänge, mit denen Funktionen des Endeffektors angesteuert werden können.
Näheres unter http://www.elmomc.com.
- erfüllt -> EL_004
- erfüllt -> EL_005
- erfüllt -> EL_017
- enthält -> R49
- schreibt und liest -> R69
- schreibt und liest -> R70
- schreibt und liest -> R83
- schreibt -> R72
- schreibt -> R79
- liest -> R68

#### R45: Beschleunigungs-Sensor (Akteur (Rolle, Funktion))
- erfüllt -> EL_034
- schreibt -> R77
- liest -> R66

#### R46: CAN-Transmitter (Akteur (Rolle, Funktion))
Endstelle der Übertragung von CAN Busnachrichten zwischen zentraler Robotersteuerung und dezentraler Achssteuerung.
- erfüllt -> EL_029
- schreibt und liest -> R69
- schreibt und liest -> R83

#### R47: Elektro-Magnet (Akteur (Rolle, Funktion))
- erfüllt -> EL_022
- schreibt -> R66
- schreibt -> R75
- liest -> R79

#### R48: Elektromotor (Akteur (Rolle, Funktion))
- schreibt -> R75
- liest -> R79

#### R49: Endeffektor mit Steuerung (Akteur (Rolle, Funktion))
- erfüllt -> EL_035
- erfüllt -> EL_036
- liest -> R72

#### R50: Endstufe Elektro-Magnet (Akteur (Rolle, Funktion))
Ein Kandidat für die Leistungsschalter ist Texas Instruments DRV8432.
- erfüllt -> EL_022
- erfüllt -> EL_001
- erfüllt -> EL_002
- erfüllt -> EL_018
- erfüllt -> EL_004
- erfüllt -> EL_005
- erfüllt -> EL_017
- erfüllt -> EL_013
- erfüllt -> EL_010
- enthält -> R67
- enthält -> R73
- enthält -> R76
- enthält -> R80
- schreibt und liest -> R71
- schreibt -> R79
- schreibt -> R80
- liest -> R76

#### R51: Magnetlager-Steuerung (Akteur (Rolle, Funktion))
- 6 Endstufen für Elektromagneten (ggf. als 'gekürzte' Variante mit 2 Endstufen für passive Magnetlager herzustellen)
- Integrierte Steuerung und Regelung auf Huckepack-Platine
- erfüllt -> EL_009
- erfüllt -> EL_014
- erfüllt -> EL_030
- erfüllt -> EL_025
- enthält -> R50
- enthält -> R71
- enthält -> R57
- enthält -> R76
- enthält -> R80
- enthält -> R81
- schreibt und liest -> R78
- schreibt und liest -> R83

#### R52: Positions-Regler (Akteur (Rolle, Funktion))

#### R53: Positions-Sensor für Antrieb (Akteur (Rolle, Funktion))
Positions-Encoder mit absolutem Meßwert.
- schreibt -> R68
- liest -> R75

#### R54: Positions-Sensor für Magnetlager (Akteur (Rolle, Funktion))
Analoge Distanzmessung.
- erfüllt -> EL_038
- erfüllt -> EL_039
- erfüllt -> EL_040
- schreibt -> R77
- liest -> R75

#### R55: Prozessor Lageregelung (Akteur (Rolle, Funktion))
Signalprozessor der Familie F28M3x Concerto von Texas Instruments, konkret f28m35h52. Näheres unter: http://www.ti.com.
(Sollte es aus Sicht des Elektronik-Entwicklers Gründe für eine andere Wahl geben, bitten wir um einen Vorschlag.)
- erfüllt -> EL_027
- schreibt und liest -> R69
- schreibt und liest -> R71
- schreibt und liest -> R82
- schreibt -> R67
- schreibt -> R76
- liest -> R77
- liest -> R80
- liest -> R81

#### R56: Prozessor Sicherheits-Funktionen (Akteur (Rolle, Funktion))
- Gibt den Antrieb frei, wenn die Magnetlagerung aktiv ist.
- Unterbricht Antrieb und Magnetlagerung bei Notaus u.ä.
- Ausgewählt: msp430G2131 (http://www.ti.com/product/msp430g2131)
- erfüllt -> EL_027
- schreibt und liest -> R70
- schreibt und liest -> R71

#### R57: Prozessorplatine Lageregelung (Akteur (Rolle, Funktion))
Mit Steckpfosten auf der Platine Magnetlager-Steuerung befestigt. Es gibt weiterhin Stecker für CAN-Bus, analoge Sensor-Signale sowie Digital-IO.
- erfüllt -> EL_011
- erfüllt -> EL_012
- erfüllt -> EL_016
- erfüllt -> EL_019
- erfüllt -> EL_030
- erfüllt -> EL_025
- enthält -> R55
- enthält -> R69
- enthält -> R77
- enthält -> R82
- schreibt und liest -> R69
- schreibt und liest -> R71
- schreibt -> R76
- liest -> R77
- liest -> R80

#### R58: Schlitten (Akteur (Rolle, Funktion))
- schreibt -> R66
- schreibt -> R75

#### R59: Spannungswandler 24V (Akteur (Rolle, Funktion))
- erfüllt -> EL_037
- erfüllt -> EL_028

#### R60: Spannungswandler 3,3V (Akteur (Rolle, Funktion))
- erfüllt -> EL_037
- erfüllt -> EL_028

#### R61: Spannungswandler 5V (Akteur (Rolle, Funktion))
- erfüllt -> EL_037
- erfüllt -> EL_028

#### R62: Strom-Regler (Akteur (Rolle, Funktion))

#### R63: Strom-Sensor (Akteur (Rolle, Funktion))
- liest -> R79

#### R64: Verteiler (Akteur (Rolle, Funktion))
Die Verteilerplatine wird es in verschiedenen Ausführungen oder Bestückungsvarianten je nach Anforderungen der jeweiligen Achse geben.
- erfüllt -> EL_016
- erfüllt -> EL_023
- erfüllt -> EL_008
- erfüllt -> EL_024
- enthält -> R44
- enthält -> R46
- enthält -> R56
- enthält -> R59
- enthält -> R60
- enthält -> R61
- enthält -> R69
- enthält -> R70
- schreibt und liest -> R74
- schreibt und liest -> R78

### R65: Typ 'Zustand' (Ordner)
Ein 'Zustand' ist ein fundamentaler Modellelement-Typ für ein passives Objekt, z.B. ein Wert, eine Bedingung, ein Informationsspeicher oder eine physische Beschaffenheit.

#### R66: Beschleunigung (Zustand (Information))

#### R67: Betriebsart (Zustand (Information))
Binärsignale zur Einstellung der Betriebsart je Endstufe:
- Aktiv/Inaktiv (Schalter offen/geschlossen)
- Vorwärts/Rückwärts
- erfüllt -> EL_001
- erfüllt -> EL_002
- erfüllt -> EL_018

#### R68: BiSS (Zustand (Information))
Digital serial interface for sensors and actuators (http://www.biss-interface.com/about.php).

#### R69: CAN (Zustand (Information))
Controller Area Network (http://en.wikipedia.org/wiki/CAN_bus).
- erfüllt -> EL_026
- enthält -> R83

#### R70: DIO Antrieb (Zustand (Information))
Eingang der Antriebssteuerung:
- STO (Safety Torque Off)
Ausgang der Antriebssteuerung:
- Error („Motor aus“ bzw. Position kann nicht mehr gehalten werden).
- erfüllt -> EL_026

#### R71: DIO Magnetlager (Zustand (Information))
Eingangssignale des Magnetlagers:
- 1 Enable (= /Emergency-Stop), wirkt als Freigabe direkt auf die Endstufe
- 1 /Motor-Error, wird an ein binäres Eingangssignal des Prozessors gelegt.
Ausgangssignale des Magnetlagers:
- 1 Floating (alle vom Prozessor geregelten Freiheitsgrade schweben)
- erfüllt -> EL_014
- erfüllt -> EL_026

#### R72: Endeffektor-Signale (Zustand (Information))
Stecker mit folgenden Kontakten:
- 24V für die Last
- 2 binäre Ausgänge ('open collector')
- 1 binärer Eingang
- GND

#### R73: Freigabe (Zustand (Information))
Extern zugeführtes binäres Freigabesignal (Enable).
- erfüllt -> EL_014

#### R74: Haupt-Versorgung (Zustand (Information))
48V geglättete Gleichspannung.
- erfüllt -> EL_023

#### R75: Position (Zustand (Information))

#### R76: PWM-Signal (Zustand (Information))
Pulsweiten-moduliertes Signal für die proportionale Ansteuerung der Endstufe.

#### R77: Sensor-Signale (Zustand (Information))
Universelle Schnittstelle für analoge Sensor-Signale
- erfüllt -> EL_011
- erfüllt -> EL_026

#### R78: Spannungs-Versorgung Magnetlager (Zustand (Information))
auch als 'POWER AMB' bezeichnet.
- Magnetlager (48V)
- Sensorik (z.B. 24V/4W im Falle der atm. X-Achse)
- Digital (5V)
- Prozessor (3,3V)
- 4x GND, getrennt für jede Spannungsquelle.
- erfüllt -> EL_026

#### R79: Strom (Zustand (Information))
- erfüllt -> EL_013

#### R80: Strom-Signal (Zustand (Information))
Messwert für Laststrom.
- erfüllt -> EL_013

#### R81: Temperatur-Signal (Zustand (Information))
SPI-Bussignal für Temperatursensor am Kühlkörper.

#### R82: U-DIO (Zustand (Information))
Universelle Digital-IO Signale für Erweiterungen.
- erfüllt -> EL_012

#### R83: Wireless CAN (Zustand (Information))

### R84: Typ 'Ereignis' (Ordner)
Ein 'Ereignis' ist ein fundamentaler Modellelement-Typ für eine zeitliche Referenz, eine Änderung einer Bedingung bzw. eines Zustandes oder generell ein Synchronisations-Mittel.
